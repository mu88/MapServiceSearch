FME workspace MapServiceSearch_CreateIndex.fmw
Title: MapServiceSearch_CreateIndex
Description: Create the Elasticsearch index for the app 'Map Service Search'.
This Workspace retrieves the datasources of all ArcGIS Server MapServices. The ArcGIS Servers to be analyzed can be configured with a JSON object, stored as a Private Parameter. After retrieving all the datasources, they will be processed and finally exported as JSON objects into the Elasticsearch index.

Parameters:
- ElasticsearchURL = https://mapservicesearch/api   # Elasticsearch-URL
- ServerUsername = admin   # Username of the ArcGIS Server Site Administrator
- ServerPassword =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   # Password of the ArcGIS Server Site Administrator
- Servers = { 	"servers": [{ 		"name": "serverA.demo.org", 		"environment": "PRD", 		"type": "Intranet" 	}, 	{ 		"name": "serverB.demo.org", 		"environment": "Staging", 		"type": "Internet" 	}] }   # Server

Note: Retrieving the ArcGIS Server Token, / so that the following request can / use this Token to authenticate against / the ArcGIS Server Admin REST API. / Attention: username and password / are sent unencrypted, so use HTTPS!
AGSTokenRetriever
    PROTOCOL = https
    SERVERNAME = @Value(ServerName)
    SERVERPASSWORD = $(ServerPassword)
    SERVERUSERNAME = $(ServerUsername)
    Token -> AGSServiceRetriever
Note: Retrieve ALL services / on the ArcGIS Server
AGSServiceRetriever
    PROTOCOL = https
    SERVERNAME = @Value(ServerName)
    TOKEN = @Value(Token)
    Services -> Tester
Note: We are only interested in custom MapServices, / so we exclude the ArcGIS Server system / folders 'Utilities' and 'System' and filter all / services having the type 'MapServer'.
Tester
    BOOL_OP = AND
    TEST_CLAUSE:
      TEST @Value(FolderName) NOT_IN Utilities,System
      TEST @Value(ServiceType) = MapServer
    PASSED -> AGSMapServiceDatasourceRetriever
Note: Retrieve the actual datasources.
AGSMapServiceDatasourceRetriever
    PROTOCOL = https
    SERVERNAME = @Value(ServerName)
    SERVICENAME = @Value(QualifiedServiceName)
    TOKEN = @Value(Token)
    DataSources -> JSONTemplater_2 [DATASOURCES]
    DataSources -> Aggregator

Bookmark: Composition of the ArcGIS Servers and reset of the Elasticsearch index
  The ArcGIS Servers to be analyzed, which are stored in the Private Parameter Servers as a JSON object, will be splitted into several independent FME features. With this, the configuration of the servers to be analyzed is relatively generic, since you only have to modify the JSON object and not the Workspace itself.
  Furthermore, the Elasticsearch index will be deleted so that he can be filled afterwards 'from scratch'.
  Elasticsearch supports so-called Aggregations, which can be compared with groups in SQL. In the client, groups/Aggregations are used to request all distinct values of the fields 'serverEnvironment' and 'serverType' to fill the dropdown lists. In SQL, it would like this:
  SELECT ServerType FROM Elements GROUP BY ServerType;
  SELECT ServerEnvironment FROM Elements GROUP BY ServerEnvironment;
  To empower Elasticsearch to support these requests, the configuration of the fields 'serverEnvironment' and 'serverType' has to be modified/extended once with a single POST request.
Creator
    GEOMTYPE = Geometry Object
    NUM = 1
    CREATED -> HTTPCaller
Note: Both Ports are forwarded here since / it is possible that the search index / does not exist at all. In this case, the / DELETE request will fail, so we have / to handle this.
HTTPCaller
    CONNECTION_TIMEOUT_LENGTH = 60
    ERROR_ATTR = _error
    FOLLOW_REDIRECTS = Yes
    HTTP_METHOD = DELETE
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch
    TRANSFER_TIMEOUT_LENGTH = 90
    UPLOAD_CONTENT_TYPE = Text (text/plain)
    UPLOAD_TYPE = Specify Upload Body
    USE_COOKIES = No
    VERIFY_SSL_CERTIFICATES = Yes
    -> HTTPCaller_4
    <Rejected> -> HTTPCaller_4
Note: Create index
HTTPCaller_4
    CONNECTION_TIMEOUT_LENGTH = 60
    ERROR_ATTR = _error
    FOLLOW_REDIRECTS = Yes
    HTTP_METHOD = PUT
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch
    TRANSFER_TIMEOUT_LENGTH = 90
    UPLOAD_CONTENT_TYPE = JSON (application/json)
    UPLOAD_TYPE = Specify Upload Body
    USE_COOKIES = No
    VERIFY_SSL_CERTIFICATES = Yes
    -> HTTPCaller_5
    <Rejected> -> Terminator_3
Note: Modify index defintion / to support aggregations
HTTPCaller_5
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch/_mapping/mss
    TRANSFER_TIMEOUT_LENGTH = 90
    UPLOAD_BODY:
      {
         "mss": {
            "properties": {
              "serverType": {
                "type": "text",
                "fielddata": true
              },
               "serverEnvironment": {
                "type": "text",
                "fielddata": true
              }
            }
         }
      }
    UPLOAD_CONTENT_TYPE = JSON (application/json)
    UPLOAD_TYPE = Specify Upload Body
    USE_COOKIES = No
    VERIFY_SSL_CERTIFICATES = Yes
    -> AttributeCreator
    <Rejected> -> Terminator_4
AttributeCreator
    ATTR_TABLE = SET_TO Servers = $(Servers)
    -> JSONFragmenter
JSONFragmenter
    EXPLODE_FORMAT = JSON
    EXTRACT_ATTR = No
    JSON_ATTR = Servers
    JSON_QUERY = json["servers"][*]
    FRAGMENTS -> JSONExtractor
JSONExtractor
    EXTRACT_QUERY_TABLE = ServerName json["name"] ServerEnvironment json["environment"] ServerType json["type"]
    JSON_DOCUMENT = @Value(Servers)
    EVALUATED -> AttributeRemover
AttributeRemover
    REMOVE_ATTRS = json_type,json_index,Servers
    -> AGSTokenRetriever
Terminator_4
    MESSAGE = HTTP request to modify index definition failed.
Terminator_3
    MESSAGE = HTTP request to create index failed.

Bookmark: Group by MapService and Server, afterwards create JSON objects
  At first, we group everything by (MapService, Server), since each entry in the search index should represent a single MapService of an ArcGIS Server.
  Afterwards, we merge the grouped data with the ungrouped MapService data. During this, each grouped record gets assigned the matching records of MapService out of the ungrouped data. Within the JSONTemplater, the nested objects will be converted into a JSON object where the ungrouped data (the actual datasources) are used as a JSON array for each grouped element (the MapService of a server).
Aggregator
    ACCUM_ATTRS_NAME = Merge Incoming Attributes
    GROUP_BY = ServiceName ServerName
    LIST_NAME = Datasources
    MODE = Attributes Only
    ORDERED = No
    SEP = ,
    AGGREGATE -> JSONTemplater_2 [ROOT]
JSONTemplater_2
    DATASOURCES_QUERY_EXPR:
      {
          "datasource" : fme:get-attribute("Datasource"),
          "datasourceType" : fme:get-attribute("DatasourceType"),
          "datasourceAuthentication" : fme:get-attribute("DatasourceAuthenticationType"),
          "datasourceUser" : fme:get-attribute("DatasourceUser"),
          "datasetName" : fme:get-attribute("DatasetName")
      }
    RESULT_ATTRIBUTE = _result
    ROOT_QUERY_EXPR:
      {
          "serverName" : fme:get-attribute("ServerName"),
          "serverEnvironment" : fme:get-attribute("ServerEnvironment"),
          "serverType" : fme:get-attribute("ServerType"),
          "folderName" : fme:get-attribute("FolderName"),
          "serviceName" : fme:get-attribute("ServiceName"),
          "datasources" : [
              fme:process-features("DATASOURCES",
                  ("ServerName", "ServerEnvironment", "ServerType", "ServiceName"),
                  ( fme:get-attribute("ServerName"), fme:get-attribute("ServerEnvironment"), fme:get-attribute("ServerType"), fme:get-attribute("ServiceName") ) )
          ]
      }
    VISIBLE_QUERY_VALIDATE = Yes
    -> JSONValidator

Bookmark: Conversion of the desired information into JSON objects for the Elasticsearch index
JSONValidator
    ERROR_LIST_ATTR = _json_error
    JSON_DOCUMENT = @Value(_result)
    PASSED -> HTTPCaller_2
    FAILED -> Terminator
Note: POST request to add an entry / to the search index
HTTPCaller_2
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch/mss
    TRANSFER_TIMEOUT_LENGTH = 90
    UPLOAD_BODY = @Value(_result)
    UPLOAD_CONTENT_TYPE = JSON (application/json)
    UPLOAD_TYPE = Specify Upload Body
    USE_COOKIES = No
    VERIFY_SSL_CERTIFICATES = Yes
    <Rejected> -> Terminator_2
Terminator_2
    MESSAGE = POST-Request to add entry to index failed
Terminator
    MESSAGE = JSON Validation failed

FME custom transformer AGSServiceRetriever

Parameters:
- PROTOCOL = https   # Protocol
- SERVERNAME = serverA   # Name of the ArcGIS Server
- TOKEN =   # Token of the ArcGIS Server Site Administrator

Input (input)
    -> HTTPCaller_2
Note: Retrieve all services and folders / from the root folder
HTTPCaller_2
    ADDITIONAL_URL_PARAMETERS = f;json token;$(TOKEN)
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = $(PROTOCOL)://$(SERVERNAME)/arcgis/admin/services
    TRANSFER_TIMEOUT_LENGTH = 90
    USE_COOKIES = No
    VERIFY_SSL_CERTIFICATES = Yes
    -> JSONFragmenter
    -> JSONFragmenter_2
    <Rejected> -> Terminator
Note: Split services into / single FME features
JSONFragmenter_2
    EXPLODE_FORMAT = JSON
    EXTRACT_ATTR = No
    JSON_ATTR = _response_body
    JSON_QUERY = json["services"][*]
    FRAGMENTS -> JSONExtractor_2
Note: Extract name and type / of the service
JSONExtractor_2
    EXTRACT_QUERY_TABLE = ServiceName json["serviceName"] ServiceType json["type"]
    JSON_DOCUMENT = @Value(_response_body)
    EVALUATED -> AttributeCreator_3
Note: Here we construct a helper string / which contains a combination of / folder, service name and service type. / This makes the following HTTP / request easier since possibly existing / folder is already included.
AttributeCreator_3
    ATTR_TABLE = SET_TO QualifiedServiceName = FME_CONDITIONAL:DEFAULT_VALUE'@Value(FolderName)/@Value(ServiceName).@Value(ServiceType)'BOOL_OP;OR;COMPOSITE_TEST;<Unused>;TEST @Value(FolderName) NOT_ATTRIBUTE_HAS_VALUE _FME_BLANK_STRING_'@Value(ServiceName).@Value(ServiceType)'FME_NUM_CONDITIONS2___
    -> AttributeRemover
AttributeRemover
    LIST_ATTRS = _headers{} _headers{}.name _headers{}.value
    REMOVE_ATTRS = _http_status_code,_response_body,json_type,json_index
    -> Services (output)
Services (output)
Terminator
    MESSAGE = Error while retrieving services

Bookmark: Retrieve services in folders
  Since services can be published into folders, all services within the previously determined folders are retrieved. Actually ArcGIS Server doesn't support folders in folders, so a recursive traverse of the folder tree is not necessary.
JSONFragmenter
    EXPLODE_FORMAT = JSON
    EXTRACT_ATTR = No
    JSON_ATTR = _response_body
    JSON_QUERY = json["folders"][*]
    FRAGMENTS -> AttributeCreator_2
AttributeCreator_2
    ATTR_TABLE = SET_TO FolderName = @Value(_response_body)
    -> HTTPCaller_3
HTTPCaller_3
    ADDITIONAL_URL_PARAMETERS = f;json token;$(TOKEN)
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = $(PROTOCOL)://$(SERVERNAME)/arcgis/admin/services/@Value(FolderName)
    TRANSFER_TIMEOUT_LENGTH = 90
    USE_COOKIES = No
    VERIFY_SSL_CERTIFICATES = Yes
    -> JSONFragmenter_2
    <Rejected> -> Terminator

FME custom transformer AGSTokenRetriever

Parameters:
- PROTOCOL = https   # Protocol
- SERVERNAME = serverA   # " " Name of the ArcGIS Server
- SERVERUSERNAME = admin   # Username of the ArcGIS Server Site Administrator
- SERVERPASSWORD = secret   # Password of the ArcGIS Server Site Administrator

Input (input)
    -> HTTPCaller
Note: Transmission of username and password / to the ArcGIS Server for Token creation. / Attention: UNENCRYPTED
HTTPCaller
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(PROTOCOL)://$(SERVERNAME)/arcgis/admin/generateToken
    TRANSFER_TIMEOUT_LENGTH = 90
    UPLOAD_BODY = username=$(SERVERUSERNAME)&password=$(SERVERPASSWORD)&client=requestip&f=json
    UPLOAD_CONTENT_TYPE = application/x-www-form-urlencoded
    UPLOAD_TYPE = Specify Upload Body
    USE_COOKIES = No
    VERIFY_SSL_CERTIFICATES = Yes
    -> JSONExtractor
    <Rejected> -> Terminator
Note: Extract the Token
JSONExtractor
    EXTRACT_QUERY_TABLE = Token json["token"]
    JSON_DOCUMENT = @Value(_response_body)
    EVALUATED -> AttributeRemover
AttributeRemover
    LIST_ATTRS = _headers{} _headers{}.name _headers{}.value
    REMOVE_ATTRS = _http_status_code,_response_body
    -> Token (output)
Token (output)
Terminator
    MESSAGE = Error while retrieving token

FME custom transformer AGSMapServiceDatasourceRetriever

Parameters:
- PROTOCOL =   # Protocol
- SERVERNAME =   # Name of the ArcGIS Server
- TOKEN =   # Token of the ArcGIS Server Site Administrator
- SERVICENAME =   # Name of the service

Input (input)
    -> HTTPCaller
Note: Retrieve the service manifest / which contains all datasources
HTTPCaller
    ADDITIONAL_URL_PARAMETERS = f;json token;$(TOKEN)
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = $(PROTOCOL)://$(SERVERNAME)/arcgis/admin/services/$(SERVICENAME)/iteminfo/manifest/manifest.json
    TRANSFER_TIMEOUT_LENGTH = 90
    USE_COOKIES = No
    VERIFY_SSL_CERTIFICATES = Yes
    -> JSONFragmenter_2
    <Rejected> -> Terminator_2
Note: Split into different databases / per service
JSONFragmenter_2
    EXPLODE_FORMAT = JSON
    EXTRACT_ATTR = No
    JSON_ATTR = _response_body
    JSON_QUERY = json["databases"][*]
    FRAGMENTS -> JSONExtractor
Note: Extract type and location / of the datasource
JSONExtractor
    EXTRACT_QUERY_TABLE = onServerWorkspaceFactoryProgID json["onServerWorkspaceFactoryProgID"] onServerConnectionString json["onServerConnectionString"]
    JSON_DOCUMENT = @Value(_response_body)
    EVALUATED -> JSONFragmenter_3
Note: Split into different records / per database
JSONFragmenter_3
    EXPLODE_FORMAT = JSON
    EXTRACT_ATTR = No
    JSON_ATTR = _response_body
    JSON_QUERY = json["datasets"][*]
    FRAGMENTS -> JSONExtractor_2
Note: Extract name of the / datasource
JSONExtractor_2
    EXTRACT_QUERY_TABLE = onServerName json["onServerName"]
    JSON_DOCUMENT = @Value(_response_body)
    EVALUATED -> AttributeValueMapper
Note: Retrieve name of the record
AttributeCreator_3
    ATTR_TABLE = SET_TO DatasetName = @Value(onServerName)
    -> AttributeRemover
AttributeRemover
    LIST_ATTRS = DatabaseMatches{} DatabaseMatches{}.part DatabaseMatches{}.startIndex InstanceMatches{} InstanceMatches{}.part InstanceMatches{}.startIndex UserMatches{} UserMatches{}.part UserMatches{}.startIndex _headers{} _headers{}.name _headers{}.value
    REMOVE_ATTRS = _http_status_code,onServerConnectionString,_response_body,json_type,onServerName,onServerWorkspaceFactoryProgID,json_index
    -> DataSources (output)
DataSources (output)
Terminator
    MESSAGE = WorkspaceType '@Value(onServerWorkspaceFactoryProgID)' is not handled
Terminator_2
    MESSAGE = Error while retrieving manifest for service '$(SERVICENAME)'

Bookmark: Split into different types of datasources
  With the help of a dedicated attribute, the type of datasource is determined so that they can be processed type-specific afterwards.
AttributeValueMapper
    DIRECTION = Forward (Source To Destination)
    LUT = esriDataSourcesGDB.FileGDBWorkspaceFactory.1,FGDB,esriDataSourcesRaster.RasterWorkspaceFactory.1,Raster,esriDataSourcesGDB.SdeWorkspaceFactory.1,SDE
    SRC = onServerWorkspaceFactoryProgID
    VAL_ATTR = DatasourceType
    -> TestFilter
TestFilter
    DEFAULT_VALUE = <UNFILTERED>
    TEST_LIST = BOOL_OP,OR,COMPOSITE_TEST,<Unused>,TEST_CLAUSE,"TEST @Value(DatasourceType) = SDE",SDE,BOOL_OP,OR,COMPOSITE_TEST,<Unused>,TEST_CLAUSE,"TEST @Value(DatasourceType) = Raster",Raster,BOOL_OP,OR,COMPOSITE_TEST,<Unused>,TEST_CLAUSE,"TEST @Value(DatasourceType) = FGDB",FGDB
    SDE -> StringSearcher
    Raster -> StringSearcher_3
    FGDB -> StringSearcher_3
    <UNFILTERED> -> Terminator

Bookmark: SDE
  Retrieve SDE-specific parameters like username of the database connection, etc.
Note: Retrieve database name
StringSearcher
    CASE = yes
    MATCHED_PARTS_ATTR = InstanceMatches
    REGEXP = ;INSTANCE=([^;]+);
    STRING_TO_SEARCH = @Value(onServerConnectionString)
    MATCHED -> StringSearcher_4
    NOT_MATCHED -> StringSearcher_4
AttributeCreator_4
    ATTR_TABLE:
      SET_TO Datasource = @Value(InstanceMatches{0}.part)
      SET_TO DatasourceAuthenticationType = Operating System Authentication
    -> AttributeCreator_3
Note: Retrieve username / of the database connection
StringSearcher_2
    CASE = yes
    MATCHED_PARTS_ATTR = UserMatches
    REGEXP = ;USER=([^;]+);
    STRING_TO_SEARCH = @Value(onServerConnectionString)
    MATCHED -> AttributeCreator
    NOT_MATCHED -> AttributeCreator
AttributeCreator
    ATTR_TABLE:
      SET_TO Datasource = @Value(InstanceMatches{0}.part)
      SET_TO DatasourceUser = @Value(UserMatches{0}.part)
      SET_TO DatasourceAuthenticationType = Database Authentication
    -> AttributeCreator_3

Bookmark: Detect authentication mode of the connection
StringSearcher_4
    CASE = yes
    MATCHED_PARTS_ATTR = AMMatches
    REGEXP = AUTHENTICATION_MODE=([^;]+)
    STRING_TO_SEARCH = @Value(onServerConnectionString)
    MATCHED -> TestFilter_2
    NOT_MATCHED -> TestFilter_2
TestFilter_2
    DEFAULT_VALUE = <UNFILTERED>
    TEST_LIST = BOOL_OP,OR,COMPOSITE_TEST,<Unused>,TEST_CLAUSE,"TEST @Value(AMMatches{0}.part) = OSA",OSA
    OSA -> AttributeCreator_4
    <UNFILTERED> -> StringSearcher_2

Bookmark: Raster and File Geodatabase
  Retrieve Raster- and FGDB-specific parameters like location, etc.
StringSearcher_3
    CASE = yes
    MATCHED_PARTS_ATTR = DatabaseMatches
    REGEXP = DATABASE=(.*)
    STRING_TO_SEARCH = @Value(onServerConnectionString)
    MATCHED -> AttributeCreator_2
    NOT_MATCHED -> AttributeCreator_2
AttributeCreator_2
    ATTR_TABLE = SET_TO Datasource = @Value(DatabaseMatches{0}.part)
    -> AttributeCreator_3

FME workspace MapServiceSearch_CreateIndex.fmw

Parameters:
- ElasticsearchURL = https://secret.searchly.com   # Elasticsearch-URL

Creator
    GEOMTYPE = Geometry Object
    NUM = 1
    CREATED -> HTTPCaller
HTTPCaller
    CONNECTION_TIMEOUT_LENGTH = 60
    ERROR_ATTR = _error
    FOLLOW_REDIRECTS = Yes
    HTTP_METHOD = DELETE
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch
    TRANSFER_TIMEOUT_LENGTH = 90
    UPLOAD_CONTENT_TYPE = Text (text/plain)
    UPLOAD_TYPE = Specify Upload Body
    USE_COOKIES = No
    VERIFY_SSL_CERTIFICATES = Yes
    -> HTTPCaller_4
    <Rejected> -> HTTPCaller_4
HTTPCaller_4
    CONNECTION_TIMEOUT_LENGTH = 60
    ERROR_ATTR = _error
    FOLLOW_REDIRECTS = Yes
    HTTP_METHOD = PUT
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch
    TRANSFER_TIMEOUT_LENGTH = 90
    UPLOAD_CONTENT_TYPE = JSON (application/json)
    UPLOAD_TYPE = Specify Upload Body
    USE_COOKIES = No
    VERIFY_SSL_CERTIFICATES = Yes
    -> HTTPCaller_5
HTTPCaller_5
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch/_mapping/mss
    TRANSFER_TIMEOUT_LENGTH = 90
    UPLOAD_BODY:
      {
         "mss": {
            "properties": {
              "serverType": {
                "type": "text",
                "fielddata": true
              },
               "serverEnvironment": {
                "type": "text",
                "fielddata": true
              }
            }
         }
      }
    UPLOAD_CONTENT_TYPE = JSON (application/json)
    UPLOAD_TYPE = Specify Upload Body
    USE_COOKIES = No
    VERIFY_SSL_CERTIFICATES = Yes
    -> FeatureReader [INITIATOR]
FeatureReader
    ATTRIBUTES = Tabelle1,"DatasetName,Datasource,DatasourceUser,DatasourceAuthenticationType,QualifiedServiceName,ServerName,ServerEnvironment,ServerType,FolderName,ServiceName,ServiceType,DatasourceType"
    ATTR_ACCUM_MODE = Only Use Result
    COMBINE_GEOM = Use Result
    DATASET = Data_modified.xlsx
    FEATURETYPES = Tabelle1
    FORMAT = XLSXR
    INTERACT = <No Spatial Filter>
    OUTPUT_FEATURES_DISPLAY = Schema and Data Features
    XLSXR_ALLOW_DOLLAR_SIGNS = YES
    XLSXR_CASE_SENSITIVE_FEATURE_TYPES = YES
    XLSXR_CONFIGURATION_DATASET = Data_modified.xlsx
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_SCAN_SCHEMA_IF_DYNAMIC = No
    XLSXR_SCHEMA = Tabelle1,0,DatasetName,char,27,,,1,Datasource,char,41,,,2,DatasourceUser,char,6,,,3,DatasourceAuthenticationType,char,32,,,4,QualifiedServiceName,char,37,,,5,ServerName,char,28,,,6,ServerEnvironment,char,8,,,7,ServerType,char,9,,,8,FolderName,string,,,,9,ServiceName,char,27,,,10,ServiceType,char,10,,,11,DatasourceType,char,7,,,1,,,,NO,NO,1,Data_modified.xlsx,"0,0,11,56",,NO,NO
    XLSXR_TABLELIST = Tabelle1
    XLSXR_USE_SCHEMA_OTHER_FILES = No
    Tabelle1 -> Aggregator
    Tabelle1 -> JSONTemplater_2 [DATASOURCES]
Aggregator
    ACCUM_ATTRS_NAME = Merge Incoming Attributes
    GROUP_BY = ServiceName ServerName
    LIST_NAME = Datasources
    MODE = Attributes Only
    ORDERED = No
    SEP = ,
    AGGREGATE -> JSONTemplater_2 [ROOT]
JSONTemplater_2
    DATASOURCES_QUERY_EXPR:
      {
          "datasource" : fme:get-attribute("Datasource"),
          "datasourceType" : fme:get-attribute("DatasourceType"),
          "datasourceAuthentication" : fme:get-attribute("DatasourceAuthenticationType"),
          "datasourceUser" : fme:get-attribute("DatasourceUser"),
          "datasetName" : fme:get-attribute("DatasetName")
      }
    RESULT_ATTRIBUTE = _result
    ROOT_QUERY_EXPR:
      {
          "serverName" : fme:get-attribute("ServerName"),
          "serverEnvironment" : fme:get-attribute("ServerEnvironment"),
          "serverType" : fme:get-attribute("ServerType"),
          "folderName" : fme:get-attribute("FolderName"),
          "serviceName" : fme:get-attribute("ServiceName"),
          "datasources" : [
              fme:process-features("DATASOURCES",
                  ("ServerName", "ServerEnvironment", "ServerType", "ServiceName"),
                  ( fme:get-attribute("ServerName"), fme:get-attribute("ServerEnvironment"), fme:get-attribute("ServerType"), fme:get-attribute("ServiceName") ) )
          ]
      }
    VISIBLE_QUERY_VALIDATE = Yes
    -> JSONValidator
JSONValidator
    ERROR_LIST_ATTR = _json_error
    JSON_DOCUMENT = @Value(_result)
    PASSED -> HTTPCaller_2
    FAILED -> Terminator
HTTPCaller_2
    CONNECTION_TIMEOUT_LENGTH = 60
    ERROR_ATTR = _error
    FOLLOW_REDIRECTS = Yes
    HTTP_METHOD = POST
    RESPONSE_HEADER_LIST_ATTR = _headers
    SAVE_FILE = Attribute
    STATUS_CODE_ATTR = _http_status_code
    TARGET_ATTR = _response_body
    TARGET_ATTR_ENCODING = auto-detect
    TARGET_URL = $(ElasticsearchURL)/mapservicesearch/mss
    TRANSFER_TIMEOUT_LENGTH = 90
    UPLOAD_BODY = @Value(_result)
    UPLOAD_CONTENT_TYPE = JSON (application/json)
    UPLOAD_TYPE = Specify Upload Body
    USE_COOKIES = No
    VERIFY_SSL_CERTIFICATES = Yes
    <Rejected> -> Terminator_2
Terminator_2
    MESSAGE = POST-Request to add entry to index failed
Terminator
    MESSAGE = JSON Validation failed
